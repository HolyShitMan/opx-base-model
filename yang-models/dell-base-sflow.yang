module dell-base-sflow {

    namespace "http://www.dellemc.com/networking/os10/dell-base-sflow";
    prefix "base-sflow";

	import dell-base-common {
        prefix "base-cmn";
    }

    organization
        "Dell EMC";

    contact
    "http://www.dell.com/support";

    description
        "sflow is a protocol used for network monitoring. This is used to provide
         a sampled flow of network information (truncated packets, interface counters etc.)
         to the network monitoring applications.This model contains a collection of
         YANG definitions provided by platform to manage sflow objects.

         Copyright (c) 2015-2018 by Dell EMC, All rights reserved.";

    revision "2018-08-17" {
        description "Fixing pyang IETF errors and adding documentation to the model.";
        reference "Network Platform Abstraction";
    }

    revision 2014-02-11 {
        description
            "Initial revision";
        reference "Network Platform Abstraction";
    }

    list entry {

        key "id";

        // Qualifier : Target

		leaf id{
			type uint32;
			description
				"Session id to uniquely identify a sflow session";
		}

        choice  if {
            case index {
                leaf ifindex {
                    type base-cmn:logical-ifindex;
                    description
                        "Interface Index which is unique across switch to identify
                        logical/physical interface";
                }
            }
            case name {
                leaf ifname {
                    type string;
                    description
                        "Interface name which is unique across switch to identify
                        logical/physical interface";
                }
            }
            description "Identity of the interface to used for the sflow.";
        }

        leaf ifindex {
            type base-cmn:logical-ifindex;
            status deprecated;
            mandatory true;
            description
                  "Interface index which uniquely identifies physical
                   interface in the switch where packet sampling needs to
                   to be enabled";
        }


        leaf direction {
            type base-cmn:traffic-path;
            mandatory true;
            description
            	"Direction of packets in which sampling needs to be enabled";
        }

        leaf sampling-rate{
        	type uint32;
            mandatory true;
            description "Rate at which packets sampling needs to be enabled";
        }
        description
            "List of sflow sessions uniquely identified by 'id'.
            Each contains a number of attributes defined here";
    }

    container socket-address {

        // Qualifier : Target

        leaf ip {
            type base-cmn:ipv4-address;
            default "127.0.0.1";
            description "socket IP address.";
        }
        leaf udp-port {
            type uint16;
            default 20001;
            description "socket port number";
        }
        description
            "Address that Sflow Applications need to open UDP socket on,
             to receive sampled packets. Sampled packets from all Sflow
             sessions are sent to a single UDP socket.";
    }
}
